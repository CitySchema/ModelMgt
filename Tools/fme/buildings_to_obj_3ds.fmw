FME workspace buildings_to_obj_3ds.fmw
Title: Buildings to Collada

Parameters:
- TileName = BOS_I_5
- tiled_exports_folder = F:\current_work\projects\Boston\Bos3d\Bos3dDevpbc\Workflows\create_grid\bos3d_masp_exports\tile_data
- DestDataset_OBJ = $(tiled_exports_folder)\bos3d_buildings_obj\$(TileName)_buildings_obj   # Destination OBJ Folder
- multipatch_source = F:\current_work\projects\Boston\Bos3d\Bos3dDevpbc\Workflows\create_grid\bos3d_masp_exports\tile_data\bos3d_gis\$(TileName)_GIS\buildings_2014_mp.shp
- DestDataset_3DS = F:\current_work\projects\Boston\Bos3d\Bos3dDevpbc\Workflows\create_grid\bos3d_masp_exports\tile_data\bos3d_buildings_3ds\$(TileName)_bldg_3ds   # Destination Autodesk 3ds Folder

Readers:
- GML_1: GML from F:\current_work\projects\Boston\Bos3d\Bos3dArchive\TileFiles\gis_data\G18\Bos3dBldg_MP_Current.shp.xml
- ESRISHAPE_2: ESRISHAPE from $(multipatch_source)

Writers:
- OBJ_1: OBJ to $(DestDataset_OBJ)
- 3DS_1: 3DS to $(DestDataset_3DS)

Bookmark: Buildings to Collada
Note: Buildings to COLLADA: This script uses a shapefile of buildings exported from ArcMap for each tile and transforms it to a Collada file. The frame is exported as well as an aid to registration of the buiodnigs with the terrain model oe with the overall tile grid. / The command line argument is the path to the tiles folder and to the folder within each tile folder that contains the shape files.
buildings_2014_mp (reader ESRISHAPE_2)
    attributes: Name char(150), Build_ID char(50), Part_ID char(50), Status char(50), Status_Not char(254), Appear_Dt date, Appear_Src char(254), Disapp_Dt date, Disapp_Src char(254), Editor char(50), Edit_Dt date, Edit_Note char(254), A80_ProjID double, A80_Name char(150), A80_Status char(150), A80_Type char(150), A80_Update date, Bldg_Use char(50), Bldg_Type char(50), IEL_Type char(50), Model_ID char(38), Model_Src char(100), ModelBatch char(254), Model_File char(254), Model_Dt date, Model_Note char(254), Model_LOD double, Survey_Dt date, Survey_Src char(150), Centr_Lat double,
      Centr_Lon double, Oblique_Ln char(254), Gnd_El_Ft double, Z_Max_Ft double, Z_MIn_Ft double, Height_Ft double, Tile char(12), Par_GIS_ID char(50), Par_Update date, Par_Yr_Blt char(25), Par_Bld_Ty char(25), Par_DOR_Co char(8), Par_Lu_Co char(20), Parcel_Use char(50), promo_cand char(254), demo_candi char(254), Merge_Inst char(254), Edit_Inst char(254), short_id char(20)
    -> GeometryValidator
GeometryValidator
    ANGULAR_TOLERANCE = 0.0
    ANGULAR_TOLERANCE_CHOICE = Automatic
    ARC_ENDPOINT_TOLERANCE = 0.0
    ARC_ENDPOINT_TOLERANCE_MODE = Auto
    CHECK_AREA_CHOICE = No
    CHECK_HOLE_TOUCHING_POLYGON = No
    CONNECT_Z_MODE_SI = First Wins
    CONNECT_Z_MODE_TR = First Wins
    DUP_COORDS_CHECK_Z = Yes
    FLIP_APPEARANCES_CHOICE = Yes
    ISSUE_ATTR_NAME = _issues
    OGC_VERSION_CHOICE = 1.2.0
    ORIENTATION_CHECK_DIR = Valid
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = Detailed
    THICKNESS_TOLERANCE = 0.0
    THICKNESS_TOLERANCE_CHOICE = Automatic
    PASSED -> Bos3dBldg_MP_Current (writer OBJ_1)
    PASSED -> AppearanceSetter [GEOMETRY]
Bos3dBldg_MP_Current (writer OBJ_1)
AppearanceSetter
    DEF_STORAGE = Create New Definitions
    DIFFUSE_COLOR = 1,1,1
    GQUERY:
      for $geom in //geometry
      where $geom/@fme_geometry_name != '"archibald"'
      return number($geom/@fme_id)
    GROUP_BY = short_id
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> buildings_2014_mp (writer 3DS_1)
buildings_2014_mp (writer 3DS_1)
