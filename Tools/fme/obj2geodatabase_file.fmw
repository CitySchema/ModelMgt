FME workspace obj2geodatabase_file.fmw

Parameters:
- SourceDataset_OBJ = F:\current_work\projects\Boston\Bos3d\Bos3dDevpbc\Workflows\ModelMgt_CityWide_20220308\ModelWork\udtg_20230130\ModelStore\obj\**\*.obj   # Source OBJ File
- FEATURE_TYPES =
- DestDataset_GEODATABASE_FILE = F:\current_work\projects\Boston\Bos3d\Bos3dDevpbc\Workflows\ModelMgt_CityWide_20220308\ModelWork\udtg_20230130\batch.gdb   # File Geodatabase

Readers:
- OBJ_1: OBJ from $(SourceDataset_OBJ) in MA83F

Writers:
- GEODATABASE_FILE_1: GEODATABASE_FILE to $(DestDataset_GEODATABASE_FILE)

BOS_2WE558Q (reader OBJ_1)
    -> FilenamePartExtractor
FilenamePartExtractor
    DIRNAME_ATTR = _dirname
    DIRPATH_ATTR = _dirpath
    EXTENSION_ATTR = _extension
    FULLNAME_ATTR = _filename
    ROOTNAME_ATTR = _rootname
    SRC_ATTR = @Value(fme_feature_type)
    -> AttributeCreator
AttributeCreator
    ATTR_TABLE = SET_TO FMEFileName = "Goodbye"
    -> Offsetter
Offsetter
    MODE = Cartesian Coordinate
    XOFF = 731100
    YOFF = 2902900
    ZOFF = 0
    OFFSET -> GeometryValidator
GeometryValidator
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> FME_from0bj2_mp (writer GEODATABASE_FILE_1)
    REPAIRED -> FME_from0bj2_mp (writer GEODATABASE_FILE_1)
FME_from0bj2_mp (writer GEODATABASE_FILE_1)
    attributes: Name char(200), random char(200)
