FME workspace ModelStore2Multipatch.fmw

Parameters:
- ModelStore = F:\current_work\projects\Boston\Bos3d\Bos3dDevpbc\Workflows\ModelMgtBPDA-20230228_v4\ModelWork\cc3d_SpotUpdates_20221222\ModelStore   # Select Input ModelStore folder
- Output_GDB = F:\current_work\projects\Boston\Bos3d\Bos3dDevpbc\Workflows\ModelMgtBPDA-20230228_v4\ModelWork\cc3d_SpotUpdates_20221222\Batch.gdb   # Destination File GDB
- DestinationFCName = FME_Validated_MP   # Destination FC Name
- SourceDataset_OBJ = $(ModelStore)\**\*.obj   # Source OBJ File

Readers:
- OBJ_2: OBJ from $(SourceDataset_OBJ)

Writers:
- GEODATABASE_FILE_1: GEODATABASE_FILE to $(Output_GDB)
- CSV2_1: CSV2 to $(ModelStore)
- GEODATABASE_FILE_2: GEODATABASE_FILE to $(Output_GDB)
- CSV2_2: CSV2 to $(ModelStore) in EPSG:2249

Note: This workbench reads all of the OBJ files in the user-specified ModelStore and writes them to a multipatch feature class. Validation logs are written to recored any repairs that were made or unrecoverable errors.
Note: Read all OBJ files in user-specified ModelStore folder.
BOS-00NUE-OWDJF-XX898 (reader OBJ_2)
    -> FilenamePartExtractor
FilenamePartExtractor
    DIRNAME_ATTR = _dirname
    DIRPATH_ATTR = _dirpath
    EXTENSION_ATTR = _extension
    FULLNAME_ATTR = _filename
    ROOTNAME_ATTR = _rootname
    SRC_ATTR = @Value(fme_feature_type)
    -> Offsetter
Note: Offset models to Mass State Plane Feet.
Offsetter
    MODE = Cartesian Coordinate
    XOFF = 731100
    YOFF = 2902900
    ZOFF = 0
    OFFSET -> GeometryValidator
GeometryValidator
    ISSUE_ATTR_NAME = _issues
    PRESETS = Custom
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR SURFACE_ORIENTATION FME_CONTROLLER_QUERY_FILE]transformers/dependencies/geometryvalidator8/SURFACE_ORIENTATION.fme]FME_CONTROLLER_CHOICE]SURFACE_ORIENTATION
    SUMMARY = Detailed
    PASSED -> FME_FromOBJ_MP (writer GEODATABASE_FILE_1)
    FAILED -> FME_FromOBJ_MP (writer GEODATABASE_FILE_1)
    FAILED -> ListExploder
    REPAIRED -> FME_FromOBJ_MP (writer GEODATABASE_FILE_1)
    REPAIRED -> ListExploder
    ISSUE_LOCATIONS -> ListExploder
    <REJECTED> -> ListExploder
Note: Write Geodatabase Feature Class
FME_FromOBJ_MP (writer GEODATABASE_FILE_1)
    attributes: _rootname char(2048)
Note: List Exploder splits the list of issues per feature into one table row per issue.
ListExploder
    ATTR_ACCUM_MODE = Merge List Attributes
    ATTR_CONFLICT_RES = Use List Attribute Values
    INDEX_ATTR = _element_index
    LIST_ATTR = _issues{}
    ELEMENTS -> NullAttributeMapper
    <REJECTED> -> NullAttributeMapper
Note: Before running this, you must make sure that the FME_Validated_MP feature class and the FMELOG_Tbl are not open in ArcGIS Pro. After closing or deletfing these, save your project. Also make sure that any active edits within the target batch.gdb have been saved.
Note: When Repair Status is Null, change it to "Repaired"
NullAttributeMapper
    ATTRCHOICE = Selected Attributes
    ATTRLIST = repair_state
    NEW_VALUE = Repaired
    NULL_TREATMENT = New Value
    SOURCE_ATTR_VAL = Null
    -> StatisticsCalculator
Note: Groups redundnat rows with same issue and feature into one row with count.
StatisticsCalculator
    CALCULATION_MODE = NUMERIC
    FEAT_STATS = issue_found,NUMERIC_MODE,,,COUNT,,,,,,,,,,
    GROUP_BY = issue_found location_sample.x location_sample.y location_sample.z repair_state _rootname
    SUMMARY -> OBJ2GDB_Validation_log (writer CSV2_2)
    SUMMARY -> OBJ2GDB_ValidationLog_TBL (writer GEODATABASE_FILE_2)
Note: Write validation log to Geodatabase
OBJ2GDB_ValidationLog_TBL (writer GEODATABASE_FILE_2)
    attributes: _rootname char(2048), issue_found char(2048), location_sample_x double, location_sample_y double, location_sample_z double, repair_state char(2048), issue_found_total_count char(20)
OBJ2GDB_Validation_log (writer CSV2_2)
    attributes: _rootname string, issue_found string, location_sample.x real64, location_sample.y real64, location_sample.z real64, repair_state string, issue_found.total_count uint64
