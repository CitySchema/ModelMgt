FME workspace Multipatch2ModelStore.fmw
Title: Export Tiled Buildings to OBJ

Parameters:
- SourceDataset_GEODATABASE_FILE = F:\current_work\projects\Boston\Bos3d\Bos3dDevpbc\Workflows\ModelMgtBPDA-20230228_v4\ModelWork\cc3d_SpotUpdates_20221222\Batch.gdb   # File Geodatabase
- SelectedFeatureClass = Prep_MP   # Select a Feature Class to Validate
- OutputModelStore = F:\current_work\projects\Boston\Bos3d\Bos3dDevpbc\Workflows\ModelMgtBPDA-20230228_v4\ModelWork\cc3d_SpotUpdates_20221222\ModelStore   # Select your ModelStore folder for output.
- Tile_Option = @Value(Tile_ID)_OBJ\@Value(Model_ID)_OBJ   # Check to sort OBJs into Tiles

Readers:
- GEODATABASE_FILE_1: GEODATABASE_FILE from $(SourceDataset_GEODATABASE_FILE)

Writers:
- CSV2_2: CSV2 to $(OutputModelStore)
- OBJ_2: OBJ to $(OutputModelStore)\obj
- GEOJSON_1: GEOJSON to $(OutputModelStore)\catalogPolys.js
- CSV2_1: CSV2 to $(OutputModelStore)

Note: Converts Multipatch models form an ArcGIS File Geodatabase into a CitySchema Model Store. / See www.cityscehma.org/repocat.
AutoAssembled_MP (reader GEODATABASE_FILE_1)
    attributes: OBJECTID integer, Name char(150), StructType char(50), Project_Id double, ProjectLnk char(512), Status char(50), Appear_Dt date, Appear_Src char(254), Disapp_Dt date, Disapp_Src char(254), Model_ID char(15), Model_Cred char(100), ModelBatch char(254), Model_File char(254), Model_Dt date, Model_Note char(254), Model_LOD double, Survey_Dt date, Survey_Src char(150), Centr_Lat double, Centr_Lon double, Centr_X_Ft double, Centr_Y_Ft float, Gnd_El_Ft double, Z_Max_Ft double, Z_MIn_Ft double, Height_Ft double, Tile_ID char(12), Parcel_ID char(15), Struct_ID char(255),
      StructUse char(50), GoogleLnk char(254), NearMapLnk char(254), Struct_Lnk char(255), Parcel_Lnk char(255), Editor char(50), Edit_Dt date, EditAction char(255), QA_Issue char(255), QA_Flag char(255), RecInitUser char(255), RecInitDt date, RecModUser char(255), RecModDt date
    -> AttributeCreator_2
AttributeCreator_2
    ATTR_TABLE:
      SET_TO FeatureClass = AutoAssembled_MP
      SET_TO SelectedFC = $(SelectedFeatureClass)
    -> TestFilter
Prep_MP (reader GEODATABASE_FILE_1)
    attributes: OBJECTID integer, Name char(150), StructType char(50), Project_ID char(25), ProjectLnk char(512), Status char(50), Appear_Dt date, Appear_Src char(254), Disapp_Dt date, Disapp_Src char(254), Model_ID char(50), Model_Cred char(100), Model_LOD double, Survey_Src char(150), Survey_Dt date, Model_Note char(254), Model_Dt date, ModelBatch char(254), Model_File char(254), ModelStore char(25), Centr_Lat double, Centr_Lon double, Centr_X_Ft double, Centr_Y_Ft float, Gnd_El_Ft double, Z_Max_Ft double, Z_MIn_Ft double, Height_Ft double, Tile_ID char(12), GoogleLnk char(254),
      NearMapLnk char(254), Parcel_ID char(15), Parcel_Lnk char(255), Struct_ID char(255), StructUse char(50), Struct_Lnk char(255), Editor char(50), Edit_Dt date, EditAction char(255), QA_Issue char(255), QA_Flag char(255), RecInitUser char(255), RecInitDt date, RecModUser char(255), RecModDt date
    -> AttributeCreator
AttributeCreator
    ATTR_TABLE:
      SET_TO FeatureClass = Prep_MP
      SET_TO SelectedFC = $(SelectedFeatureClass)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(FeatureClass) = @Value(SelectedFC)",SelectedFC
    SelectedFC -> AttributeManager
AttributeManager
    ATTR_TABLE:
      REMOVE OBJECTID
      SET_TO Model_ID = @Value(Model_ID)
      SET_TO Name = @Value(Name)
      SET_TO StructType = @Value(StructType)
      SET_TO Project_Id
      SET_TO ProjectLnk
      SET_TO Model_Cred = @Value(Model_Cred)
      SET_TO Model_Note = @Value(Model_Note)
      SET_TO Model_LOD = @Value(Model_LOD)
      SET_TO Survey_Dt = @Value(Survey_Dt)
      SET_TO Survey_Src = @Value(Survey_Src)
      SET_TO Centr_Lat = @Value(Centr_Lat)
      SET_TO Centr_Lon = @Value(Centr_Lon)
      SET_TO Centr_X_Ft = @Value(Centr_X_Ft)
      SET_TO Centr_Y_Ft = @Value(Centr_Y_Ft)
      SET_TO Gnd_El_Ft = @Value(Gnd_El_Ft)
      SET_TO Z_Max_Ft = @Value(Z_Max_Ft)
      SET_TO Z_MIn_Ft = @Value(Z_MIn_Ft)
      SET_TO Tile_ID = @Value(Tile_ID)
      SET_TO Parcel_ID
    -> catalog (writer CSV2_1)
    -> FeatureWriter_2 [<All>]
    -> SurfaceFootprintReplacer
    -> GeometryValidator_3
SurfaceFootprintReplacer
    OFFSET_Z = Minimum Z
    SHADOW_MODE = Overhead Shadow
    FOOTPRINT -> CatalogPolys.js (writer GEOJSON_1)
Note: GeoJSON ModelStore Catalog Polys
CatalogPolys.js (writer GEOJSON_1)
    attributes: OBJECTID int, Name string, StructType string, Project_ID string, ProjectLnk string, Status string, Appear_Dt string, Appear_Src string, Disapp_Dt string, Disapp_Src string, Model_ID string, Model_Cred string, Model_LOD float, Survey_Src string, Survey_Dt string, Model_Note string, Model_Dt string, ModelBatch string, Model_File string, ModelStore string, Centr_Lat float, Centr_Lon float, Centr_X_Ft float, Centr_Y_Ft float, Gnd_El_Ft float, Z_Max_Ft float, Z_MIn_Ft float, Height_Ft float, Tile_ID string, GoogleLnk string,
      NearMapLnk string, Parcel_ID string, Parcel_Lnk string, Struct_ID string, StructUse string, Struct_Lnk string, Editor string, Edit_Dt string, EditAction string, QA_Issue string, QA_Flag string, RecInitUser string, RecInitDt string, RecModUser string, RecModDt string
Note: Per-Model JSON Metadata
FeatureWriter_2
    DATASET = $(OutputModelStore)\obj\$(Tile_Option)\@Value(Model_ID).json
    DATASET_ATTR = _dataset
    FEATURE_TYPE_LIST_ATTR = _feature_type
    FORMAT = JSON
    JSON_DESTINATION_DATASETTYPE_VALIDATION = Yes
    JSON_FEATURE_TYPE_KEY = json_featuretype
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = YES
    JSON_WRITE_GEOMETRY = NO
    TOTAL_FEATURES_WRITTEN_ATTR = _total_features_written
Note: CSV ModelStore Catalog
catalog (writer CSV2_1)
    attributes: OBJECTID string, Name varchar(150), StructType varchar(50), Project_ID varchar(25), ProjectLnk varchar(512), Status varchar(50), Appear_Dt datetime, Appear_Src varchar(254), Disapp_Dt datetime, Disapp_Src varchar(254), Model_ID varchar(50), Model_Cred varchar(100), Model_LOD string, Survey_Src varchar(150), Survey_Dt datetime, Model_Note varchar(254), Model_Dt datetime, ModelBatch varchar(254), Model_File varchar(254), ModelStore varchar(25), Centr_Lat string, Centr_Lon string, Centr_X_Ft string, Centr_Y_Ft string, Gnd_El_Ft string, Z_Max_Ft string, Z_MIn_Ft string, Height_Ft string, Tile_ID varchar(12), GoogleLnk varchar(254),
      NearMapLnk varchar(254), Parcel_ID varchar(15), Parcel_Lnk varchar(255), Struct_ID varchar(255), StructUse varchar(50), Struct_Lnk varchar(255), Editor varchar(50), Edit_Dt datetime, EditAction varchar(255), QA_Issue varchar(255), QA_Flag varchar(255), RecInitUser varchar(255), RecInitDt datetime, RecModUser varchar(255), RecModDt datetime

Bookmark: Model Repair Validation and Reporting
Note: These procedures check for vaarious problems. Mny geometrical errors can be repaired. It seems as though there are many problems with surface orientation that can't be repaired, but that don;t seem to cause a problem in lots of toos we tried. I think that this is a problem inherent in mesh objects that are nto closed
Note: Look for mis-oriented faces. repair what you can. Many models fail this test, but seem to work fine in all the tools we have tried.
GeometryValidator_3
    ISSUE_ATTR_NAME = _issues
    PRESETS = Custom
    REPAIR = Yes
    RULES = SURFACE_ORIENTATION FME_CONTROLLER_QUERY_FILE]transformers/dependencies/geometryvalidator/SURFACE_ORIENTATION.fme]FME_CONTROLLER_CHOICE]SURFACE_ORIENTATION AREA_ORIENTATION AREA_ORIENTATION]VALID]FME_CONTROLLER_QUERY_FILE]transformers/dependencies/geometryvalidator/AREA_ORIENTATION.fme]FME_CONTROLLER_CHOICE]AREA_ORIENTATION
    SUMMARY = Detailed
    PASSED -> GeometryValidator
    FAILED -> GeometryValidator
    REPAIRED -> GeometryValidator
Note: Check for degenerate geometry and repair what you can.
GeometryValidator
    ISSUE_ATTR_NAME = _issues
    PRESETS = Custom
    REPAIR = Yes
    RULES = NAN_REMOVAL PROCESS_MEASURE]NO]FME_CONTROLLER_QUERY_FILE]transformers/dependencies/geometryvalidator/NAN_REMOVAL.fme]FME_CONTROLLER_CHOICE]NAN_REMOVAL NULL_REMOVAL FME_CONTROLLER_QUERY_FILE]transformers/dependencies/geometryvalidator/NULL_REMOVAL.fme]FME_CONTROLLER_CHOICE]NULL_REMOVAL TYPE_REPAIR CONNECT_Z_MODE]LAST_WINS]ARC_ENDPOINT_TOLERANCE_MODE]Auto]ARC_ENDPOINT_TOLERANCE]<Unused>]FME_CONTROLLER_QUERY_FILE]transformers/dependencies/geometryvalidator/TYPE_REPAIR.fme]FME_CONTROLLER_CHOICE]TYPE_REPAIR SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator/SELF_INTERSECTING.fme]FME_CONTROLLER_CHOICE]SELF_INTERSECTING
    SUMMARY = Detailed
    PASSED -> GeometryValidator_4
    PASSED -> GeometryPartExtractor_2
    PASSED -> AppearanceSetter [GEOMETRY]
    FAILED -> ListExploder
    FAILED -> GeometryValidator_4
    FAILED -> GeometryPartExtractor_2
    FAILED -> AppearanceSetter [GEOMETRY]
    REPAIRED -> ListExploder
    REPAIRED -> GeometryValidator_4
    REPAIRED -> GeometryPartExtractor_2
    REPAIRED -> AppearanceSetter [GEOMETRY]
    ISSUE_LOCATIONS -> ListExploder
    INVALID_PARTS -> GeometryValidator_4
    INVALID_PARTS -> GeometryPartExtractor_2
    INVALID_PARTS -> AppearanceSetter [GEOMETRY]
Note: List Exploder splits multiple issues per feature into individual table rows.
ListExploder
    ATTR_ACCUM_MODE = Merge List Attributes
    ATTR_CONFLICT_RES = Use List Attribute Values
    INDEX_ATTR = _element_index
    LIST_ATTR = _issues{}
    ELEMENTS -> NullAttributeMapper_2
    <REJECTED> -> NullAttributeMapper_2
Note: Replaces Null with "Repaired"
NullAttributeMapper_2
    ATTRCHOICE = Selected Attributes
    ATTRLIST = repair_state
    NEW_VALUE = Repaired
    NULL_TREATMENT = New Value
    REG_EXP = /^\s*$/
    SOURCE_ATTR_VAL = Empty "Missing (Selected Attributes Only)" Null
    -> StatisticsCalculator
Note: Groups rows that refer to the same issue for the same model..
StatisticsCalculator
    CALCULATION_MODE = NUMERIC
    FEAT_STATS = issue_found,NUMERIC_MODE,,,COUNT,,,,,,,,,,
    GROUP_BY = Model_ID Name issue_found location_sample.x location_sample.y location_sample.z repair_state
    SUMMARY -> GDB2OBJ_Validation_log (writer CSV2_2)
Note: Validation Log
GDB2OBJ_Validation_log (writer CSV2_2)
    attributes: Name string, Model_ID string, count string, issue_found string, location_sample.x string, location_sample.y string, location_sample.z string, repair_state string, details string, fme_rejection_code string, _element_index string
Note: This block lets us see if some of the surface orientation problems can be fixed now that geometry has been repaired. ALso allows us to log the survace orientation problems.
GeometryValidator_4
    ISSUE_ATTR_NAME = _issues
    PRESETS = Custom
    REPAIR = Yes
    RULES = SURFACE_ORIENTATION FME_CONTROLLER_QUERY_FILE]transformers/dependencies/geometryvalidator/SURFACE_ORIENTATION.fme]FME_CONTROLLER_CHOICE]SURFACE_ORIENTATION AREA_ORIENTATION AREA_ORIENTATION]VALID]FME_CONTROLLER_QUERY_FILE]transformers/dependencies/geometryvalidator/AREA_ORIENTATION.fme]FME_CONTROLLER_CHOICE]AREA_ORIENTATION
    SUMMARY = Detailed
    FAILED -> ListExploder_2
    REPAIRED -> ListExploder_2
    ISSUE_LOCATIONS -> ListExploder_2
ListExploder_2
    ATTR_ACCUM_MODE = Merge List Attributes
    ATTR_CONFLICT_RES = Use List Attribute Values
    INDEX_ATTR = _element_index
    LIST_ATTR = _issues{}

Bookmark: Surface Appearances
Note: These tool s make sure all surfaces are shaded with flat white, which is necessary for ArcGIS Pro if you want to themaitcally shade models. / ToDo: figure out how to deal with textured models.
Note: I found this method in an on-line forum. I don;t understand why it is necessary, but it is!
GeometryPartExtractor_2
    EXTRACTTYPE_PARAM = Extract
    GQUERY:
      for $geom in //geometry
      where $geom/@fme_geometry_type = 'IFMEFace'
      return number($geom/@fme_id)
    PROCESSED -> AppearanceStyler
    UNTOUCHED -> AppearanceStyler
Note: Create appearances. For now all face appearances are white. This is because of unpredictable tings happen with multipatch textures.
AppearanceStyler
    ALPHA = 1.0
    APPEARANCE_NAME = White
    DIFFUSE_COLOR = 1,1,1
    SHININESS = 0
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter [APPEARANCE]
Note: Apply appearances by face id
AppearanceSetter
    DEF_STORAGE = Create New Definitions
    SET_ON_SIDE = Front Side
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Offsetter
Note: Shift to Metro3D Coordinate Origin
Offsetter
    MODE = Cartesian Coordinate
    XOFF = -731100
    YOFF = -2902900
    ZOFF = 0
    OFFSET -> Model_ID.obj (writer OBJ_2)
Note: OBJ Files
Model_ID.obj (writer OBJ_2)

Bookmark: Import Multipatch Models
Note: FME will only import feature classes that have been hard-coded in advance. So we read both Prep_MP and AutoAssembled, and filter them according to the FC chosen by the user at run-time.

Bookmark: Write Metadata
Note: A catalog is produced for the entire model store as a CSV table and as a GeoJSON polygon dataset. Metadata is also created for each OBJ file.
