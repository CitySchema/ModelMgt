FME workspace Multipatch2Obj.fmw
Title: Export Tiled Buildings to OBJ

Parameters:
- ModelStoreFolder = S:\trash\fme\library   # Model Store Folder
- SourceDataset_GEODATABASE_FILE_3 = F:\current_work\projects\Boston\Bos3d\Bos3dDevpbc\Workflows\ModelMgt_CityWide_20220308\ModelWork\cc3d_LibraryUpdates_20221017\Batch.gdb   # File Geodatabase
- obj = $(ModelStoreFolder)   # OBJ

Readers:
- GEODATABASE_FILE_2: GEODATABASE_FILE from $(SourceDataset_GEODATABASE_FILE_3)

Writers:
- OBJ_1: OBJ to $(ModelStoreFolder)
- CSV2_2: CSV2 to $(ModelStoreFolder)

Prep_MP (reader GEODATABASE_FILE_2) [off]
    attributes: OriginalOID integer, OBJECTID integer
    -> NullAttributeMapper_3
    -> AttributeManager
    -> GeometryValidator [off]
Ready_MP (reader GEODATABASE_FILE_2)
    attributes: OBJECTID integer, Name char(150), StructType char(50), Project_Id double, ProjectLnk char(512), Status char(50), Appear_Dt date, Appear_Src char(254), Disapp_Dt date, Disapp_Src char(254), Model_ID char(15), Model_Cred char(100), ModelBatch char(254), Model_File char(254), Model_Dt date, Model_Note char(254), Model_LOD double, Survey_Dt date, Survey_Src char(150), Centr_Lat double, Centr_Lon double, Centr_X_Ft double, Centr_Y_Ft float, Gnd_El_Ft double, Z_Max_Ft double, Z_MIn_Ft double, Height_Ft double, Tile_ID char(12), Parcel_ID char(15), Struct_ID char(255),
      StructUse char(50), GoogleLnk char(254), NearMapLnk char(254), Struct_Lnk char(255), Parcel_Lnk char(255), Editor char(50), Edit_Dt date, EditAction char(255), QA_Issue char(255), QA_Flag char(255), RecInitUser char(255), RecInitDt date, RecModUser char(255), RecModDt date
    -> AttributeManager
    -> GeometryValidator [off]
    -> NullAttributeMapper_3
Note: JSON Metadata Record
FeatureWriter_5
    DATASET = $(ModelStoreFolder)\@Value(Tile_ID)\@Value(Model_ID)_OBJ.zip\@Value(Model_ID)_info.json
    DATASET_ATTR = _dataset
    FEATURE_TYPE_LIST_ATTR = _feature_type
    FORMAT = JSON
    JSON_DESTINATION_DATASETTYPE_VALIDATION = Yes
    JSON_FEATURE_TYPE_KEY = json_featuretype
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = YES
    JSON_WRITE_GEOMETRY = NO
    TOTAL_FEATURES_WRITTEN_ATTR = _total_features_written
GeometryValidator
    ISSUE_ATTR_NAME = _issues
    PRESETS = Basic Integrity
    REPAIR = Yes
    RULES = NAN_REMOVAL PROCESS_MEASURE]NO]FME_CONTROLLER_QUERY_FILE]transformers\dependencies\geometryvalidator\NAN_REMOVAL.fme NULL_REMOVAL  TYPE_REPAIR CONNECT_Z_MODE]FIRST_WINS]ARC_ENDPOINT_TOLERANCE_MODE]Auto]ARC_ENDPOINT_TOLERANCE]<Unused>]FME_CONTROLLER_QUERY_FILE]transformers\dependencies\geometryvalidator\TYPE_REPAIR.fme
    SUMMARY = Detailed
    PASSED -> GeometryPartExtractor_2
    FAILED -> ListExploder
    REPAIRED -> GeometryPartExtractor_2
    REPAIRED -> ListExploder
    ISSUE_LOCATIONS -> ListExploder
    INVALID_PARTS -> ListExploder
Note: Zipped OBJ FIle
Model_ID.zip (writer OBJ_1)
Note: Validation Log
FME_Validation_log (writer CSV2_2)
    attributes: Name string, Model_ID string, count string, issue_found string, location_sample.x string, location_sample.y string, location_sample.z string, repair_state string, details string, fme_rejection_code string, _element_index string
Note: Validation Log
FME_Validation_log00 (writer CSV2_2)
    attributes: Name string, Model_ID string, count string, issue_found string, location_sample.x string, location_sample.y string, location_sample.z string, repair_state string, details string, fme_rejection_code string, _element_index string

Bookmark: Buildings Grouped
Note: Transform Multipatch to OBJ
NullAttributeMapper_3
    ATTRCHOICE = Selected Attributes
    ATTRLIST = Appear_Dt Appear_Src Centr_Lat Centr_Lon Disapp_Dt Disapp_Src Edit_Dt EditAction Editor Gnd_El_Ft GoogleLnk Height_Ft Model_Cred Model_Dt Model_File Model_ID Model_LOD Model_Note ModelBatch Name Project_Id ProjectLnk RecInitDt RecModDt Status Struct_ID Struct_Lnk StructType StructUse Survey_Dt Survey_Src Tile_ID Z_Max_Ft Z_MIn_Ft Centr_X_Ft Centr_Y_Ft RecInitUser RecModUser
    NULL_TREATMENT = Null
    REG_EXP = /^\s*$/
    SOURCE_ATTR_VAL = Empty "Missing (Selected Attributes Only)" Null
    -> FeatureWriter_5 [<All>]
AttributeManager
    ATTR_TABLE = SET_TO Model_ID = @Value(Model_ID)
    -> GeometryValidator [off]
    -> SurfaceOnSurfaceOverlayer [SURFACE]
SurfaceOnSurfaceOverlayer
    ACCUM_ATTRS_NAME = Use Attributes From One Feature
    DEAGGREGATE_INPUT = Yes
    ENABLE_TOLERANCE = No
    GROUP_BY = Model_ID
    OVC_ATTR = _overlaps
    SURFACE -> GeometryValidator
Note: Extract faces from models that behaved abnormally in the GeometryExtractor. This step is necessary for many models seem tobe corrupt somehow. This needs to be looked into.
GeometryPartExtractor_2
    EXTRACTTYPE_PARAM = Extract
    GQUERY:
      for $geom in //geometry
      where $geom/@fme_geometry_type = 'IFMEFace'
      return number($geom/@fme_id)
    PROCESSED -> AppearanceStyler [off]
    UNTOUCHED -> AppearanceStyler
    UNTOUCHED -> AppearanceSetter [GEOMETRY]
Note: Create appearances. For now all face appearances are white. This is because of unpredictable tings happen with multipatch textures.
AppearanceStyler
    ALPHA = 1.0
    APPEARANCE_NAME = White
    DIFFUSE_COLOR = 1,1,1
    SHININESS = 0
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter [APPEARANCE]
    -> AppearanceSetter [GEOMETRY] [off]
Note: Apply appearances by face id
AppearanceSetter
    DEF_STORAGE = Create New Definitions
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Aggregator_6
    <REJECTED> -> Aggregator_6
Note: re-groups Model Faces accordng to ModelID
Aggregator_6
    ACCUM_ATTRS_NAME = Get Attributes From One Representative Feature
    AGGREGATE_TYPE = Heterogeneous Collection
    GEOM_NAME_FIELD = Model_ID
    GROUP_BY = Model_ID
    MODE = Geometry - Assemble One Level
    ORDERED = No
    SEP = ,
    AGGREGATE -> Offsetter
Note: Shift to Metro3D Coordinate Origin
Offsetter
    MODE = Cartesian Coordinate
    XOFF = -731100
    YOFF = -2902900
    ZOFF = 0
    OFFSET -> Model_ID.zip (writer OBJ_1)
Note: Write Error log for geometry validator rejects. / An attribute may fail multiple testsList Exploder / Splits the list to create one record per test message
ListExploder
    ATTR_ACCUM_MODE = Merge List Attributes
    ATTR_CONFLICT_RES = Use List Attribute Values
    INDEX_ATTR = _element_index
    LIST_ATTR = _issues{}
    ELEMENTS -> FME_Validation_log (writer CSV2_2)
    ELEMENTS -> FME_Validation_log00 (writer CSV2_2)
    <REJECTED> -> FME_Validation_log (writer CSV2_2)
    <REJECTED> -> FME_Validation_log00 (writer CSV2_2)
