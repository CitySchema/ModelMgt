FME workspace ModelCollectionToOBJCatalog.fmw
Title: Export Tiled Buildings to OBJ

Parameters:
- Tile_Name = BOS_I_3
- IssueDate = 20210806   # Issue Date (YYYYMMDD
- SourceDataset_JPEG = F:\current_work\projects\Boston\Bos3d\Bos3dDevpbc\Bos3d_City_Model_Stage\Bos3d_Tiled_Data\Bos3d_Groundplan_2011_JPG\$(Tile_Name)_Groundplan_2011.jpg   # Source JPEG File(s)
- SourceDataset_SHAPEFILE = $(inGISFldrFolder)\frame_poly.shp   # Source Esri Shapefile(s)
- inGISFldrFolder = F:\current_work\projects\Boston\Bos3d\Bos3dDevpbc\Workflows\create_grid\bos3d_masp_exports\tile_data\bos3d_gis\$(Tile_Name)_GIS   # Folder of Tiled GIS Resources
- SrcModelsShp = $(inGISFldrFolder)\bos3d_models.shp   # Source Esri Shapefile(s)
- FrameObjectName = $(TileDestinationFolder)\$(Tile_Name)_Frame_OBJ.zip   # FrameOBJName
- TiledCollectionsFolder = F:\current_work\projects\Boston\Bos3d\Bos3dDevpbc\Bos3d_City_Model_Stage\Bos3d_Tiled_Data\Bos3d_ModelCollection_OBJ   # Name of Tiled Collections Folder
- TileDestinationFolder = $(TiledCollectionsFolder)\$(Tile_Name)_ModelCollection_OBJ
- CollectionCatalogFolder = $(TileDestinationFolder)/ModelCatalog   # Name of Folder for each Tile's Catalog Resources
- SrcModelPolysShp = $(inGISFldrFolder)\Bos3d_Models_Poly.shp   # Source Esri Shapefile(s)

Readers:
- SHAPEFILE_1: SHAPEFILE from $(SrcModelsShp)
- SHAPEFILE_2: SHAPEFILE from $(SrcModelPolysShp)
- PATH_1: PATH from $(TiledCollectionsFolder)\ModelCatalogTemplate/
- JPEG_1: JPEG from $(SourceDataset_JPEG)
- SHAPEFILE_3: SHAPEFILE from $(SourceDataset_SHAPEFILE)

Writers:
- OBJ_1: OBJ to $(TileDestinationFolder)
- OBJ_2: OBJ to $(FrameObjectName)
- CSV2_1: CSV2 to $(CollectionCatalogFolder)
- FILECOPY_1: FILECOPY to $(CollectionCatalogFolder)
- JPEG_2: JPEG to $(CollectionCatalogFolder)
- CSV2_2: CSV2 to $(CollectionCatalogFolder)

frame_poly (reader SHAPEFILE_3)
    attributes: tile_id char(25), tile_label char(10), town char(50), grid_col char(10), grid_row char(10), town_code char(10), BosShift_X long, BosShift_Y long, Lat double, Lon double, MASP_X long, MASP_Y long, Shape_Leng double, Shape_Area double
    -> GeometryCoercer
    -> NullAttributeMapper_2
frame_poly (writer OBJ_2)
NullAttributeMapper_2
    ATTRCHOICE = Selected Attributes
    ATTRLIST = BosShift_X BosShift_Y grid_col grid_row Lat Lon MASP_X MASP_Y Shape_Area Shape_Leng tile_id tile_label town town_code
    NULL_TREATMENT = Null
    REG_EXP = /^\s*$/
    SOURCE_ATTR_VAL = Empty "Missing (Selected Attributes Only)" Null
    -> FeatureWriter_2 [<All>]
Note: This ModelCatalog JS is a copy of the Catalog GeoJSON but with a variable declaration in the first line This hack allows the json file to be included in an HTML page.
FeatureWriter_4
    DATASET = $(CollectionCatalogFolder)\Frame_geojson.js
    DATASET_ATTR = _dataset
    FEATURE_TYPE_LIST_ATTR = _feature_type
    FORMAT = TEXTLINE
    SELECTED_PORTS = text_line text_line00
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
Note: Building models exported from shape file multipatches because these are muchmore relaible for some reason thanthegeodatabase ones
bos3d_models (reader SHAPEFILE_1)
    attributes: Name char(150), StructType char(50), Project_Id double, ProjectLnk char(254), Status char(50), Appear_Dt date, Appear_Src char(254), Disapp_Dt date, Disapp_Src char(254), Editor char(50), Edit_Dt date, EditAction char(254), Model_ID char(15), Model_Cred char(100), ModelBatch char(254), Model_File char(254), Model_Dt date, Model_Note char(254), Model_LOD double, Survey_Dt date, Survey_Src char(150), Centr_Lat double, Centr_Lon double, Gnd_El_Ft double, Z_Max_Ft double, Z_MIn_Ft double, Height_Ft double, Tile_ID char(12), Parcel_ID char(15), Struct_ID char(254),
      StructUse char(50), GoogleLnk char(254), NearMapLnk char(254), Struct_Lnk char(254), Parcel_Lnk char(254), RecInitUsr char(254), RecInitDt date, QA_Flag char(254), QA_Issue char(254), RecModUsr char(254), RecModDt date, Centr_X_Ft double, Centr_Y_Ft double
    -> GeometryValidator
    -> bos3d_models (writer CSV2_1)
    -> NullAttributeMapper_3
Note: ListExploder / An attribute may fail multiple tests / Split the list to create one record per test message
ListExploder
    ATTR_ACCUM_MODE = Merge List Attributes
    ATTR_CONFLICT_RES = Use List Attribute Values
    INDEX_ATTR = _element_index
    LIST_ATTR = _issues{}
    ELEMENTS -> Logger
    ELEMENTS -> FME_Validation_log (writer CSV2_2)
    <REJECTED> -> Logger
    <REJECTED> -> FME_Validation_log (writer CSV2_2)
FME_Validation_log (writer CSV2_2)
    attributes: Name string, Model_ID string, count string, issue_found string, location_sample.x string, location_sample.y string, location_sample.z string, repair_state string, details string, fme_rejection_code string, _element_index string
Logger
    LOG_FEATURE = LOG_ONLY
    MAXCOORDS = 20
    MAXFEATS = 20
    SEVERITY = INFO
NullAttributeMapper_3
    ATTRCHOICE = Selected Attributes
    ATTRLIST = Appear_Dt Appear_Src Centr_Lat Centr_Lon Disapp_Dt Disapp_Src Edit_Dt EditAction Editor Gnd_El_Ft GoogleLnk Height_Ft Model_Cred Model_Dt Model_File Model_ID Model_LOD Model_Note ModelBatch Name NearMapLnk Parcel_ID Parcel_Lnk Project_Id ProjectLnk QA_Flag QA_Issue RecInitDt RecInitUsr RecModDt RecModUsr Status Struct_ID Struct_Lnk StructType StructUse Survey_Dt Survey_Src Tile_ID Z_Max_Ft Z_MIn_Ft Centr_X_Ft Centr_Y_Ft
    NULL_TREATMENT = Null
    REG_EXP = /^\s*$/
    SOURCE_ATTR_VAL = Empty "Missing (Selected Attributes Only)" Null
    -> FeatureWriter_5 [<All>]
bos3d_models (writer OBJ_1)
bos3d_models (writer CSV2_1) [off]
    attributes: Name string, StructType string, Project_Id string, ProjectLnk string, Status string, Appear_Dt string, Appear_Src string, Disapp_Dt string, Disapp_Src string, Editor string, Edit_Dt string, EditAction string, Model_ID string, Model_Cred string, ModelBatch string, Model_File string, Model_Dt string, Model_Note string, Model_LOD string, Survey_Dt string, Survey_Src string, Centr_Lat string, Centr_Lon string, Gnd_El_Ft string, Z_Max_Ft string, Z_MIn_Ft string, Height_Ft string, Tile_ID string, Parcel_ID string, Struct_ID string,
      StructUse string, GoogleLnk string, NearMapLnk string, Struct_Lnk string, Parcel_Lnk string, chgAction string, chgStatus string, chgStatDt string, chgStatSrc string, chgQAIssue string, chgFlag string, ChgEdBatch string, RecInitUsr string, RecInitDt string, ChgFlagger string, ChgFlagDt string
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> filecopy (writer FILECOPY_1)
Note: Copies catalog resources into tile folder
filecopy (writer FILECOPY_1)
    attributes: filecopy_source_dataset char(512), filecopy_dest_dataset char(512), filecopy_dest_filename char(128)
Bos3d_Models_Poly (reader SHAPEFILE_2)
    attributes: Name char(150), StructType char(50), Project_Id double, ProjectLnk char(254), Status char(50), Appear_Dt date, Appear_Src char(254), Disapp_Dt date, Disapp_Src char(254), Editor char(50), Edit_Dt date, EditAction char(254), Model_ID char(15), Model_Cred char(100), ModelBatch char(254), Model_File char(254), Model_Dt date, Model_Note char(254), Model_LOD double, Survey_Dt date, Survey_Src char(150), Centr_Lat double, Centr_Lon double, Gnd_El_Ft double, Z_Max_Ft double, Z_MIn_Ft double, Height_Ft double, Tile_ID char(12), Parcel_ID char(15), Struct_ID char(254),
      StructUse char(50), GoogleLnk char(254), NearMapLnk char(254), Struct_Lnk char(254), Parcel_Lnk char(254), RecInitUsr char(254), RecInitDt date, Centr_X_Ft double, Centr_Y_Ft double, QA_Flag char(254), QA_Issue char(254), RecModUsr char(254), RecModDt date, Z_Min double, Z_Max double
    -> NullAttributeMapper
NullAttributeMapper
    ATTRCHOICE = Selected Attributes
    ATTRLIST = Appear_Dt Appear_Src Centr_Lat Centr_Lon Centr_X_Ft Centr_Y_Ft Disapp_Dt Disapp_Src Edit_Dt EditAction Editor fme_feature_type Gnd_El_Ft GoogleLnk Height_Ft Model_Cred Model_Dt Model_File Model_ID Model_LOD Model_Note ModelBatch Name NearMapLnk Parcel_ID Parcel_Lnk Project_Id ProjectLnk RecInitDt RecInitUsr Status Struct_ID Struct_Lnk StructType StructUse Survey_Dt Survey_Src Tile_ID Z_Max_Ft Z_MIn_Ft QA_Flag QA_Issue RecModDt RecModUsr
    NULL_TREATMENT = Null
    REG_EXP = /^\s*$/
    SOURCE_ATTR_VAL = Empty "Missing (Selected Attributes Only)" Null
    -> FeatureWriter [<All>]
Note: A GeoJSON version of the Model Footprints feature class.
FeatureWriter
    DATASET = $(CollectionCatalogFolder)\ModelCatalog.geojson
    DATASET_ATTR = _dataset
    FEATURE_TYPE_LIST_ATTR = _feature_type
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
    SUMMARY -> FeatureReader [INITIATOR]
    SUMMARY -> AttributeCreator
AttributeCreator
    ATTR_TABLE = SET_TO text_line_data = var ModelCatalog =
    -> FeatureWriter_3 [text_line00]
FeatureReader
    ATTR_ACCUM_MODE = Only Use Result
    COMBINE_GEOM = Use Result
    DATASET = @Value(_dataset)
    FORMAT = TEXTLINE
    OUTPUT_FEATURES_DISPLAY = Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    <OTHER> -> FeatureHolder
FeatureHolder
    -> FeatureWriter_3 [text_line]
Note: This ModelCatalog JS is a copy of the Catalog GeoJSON but with a variable declaration in the first line This hack allows the json file to be included in an HTML page.
FeatureWriter_3
    DATASET = $(CollectionCatalogFolder)\ModelCatalog_geojson.js
    DATASET_ATTR = _dataset
    FEATURE_TYPE_LIST_ATTR = _feature_type
    FORMAT = TEXTLINE
    SELECTED_PORTS = text_line text_line00
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
JPEG (reader JPEG_1)
    -> RasterResampler
RasterResampler
    COLUMNS = 3600
    INTERPOLATION_TYPE_NAME = Bicubic
    ROWCOL_OR_CELLSIZE = RowsColumns
    ROWS = 3600
    RESAMPLED -> Offsetter_3
Offsetter_3
    MODE = Cartesian Coordinate
    XOFF = -731100
    YOFF = -2902900
    ZOFF = 0
    OFFSET -> Groundplan_2011 (writer JPEG_2)
Groundplan_2011 (writer JPEG_2)

Bookmark: Tile Frame Edges
Note: Must force coordinates to 3D, per Dave at FME
GeometryCoercer
    GQUERY:
      for $geom in //geometry
      where $geom/count(parent::geometry) = 0
      return number($geom/@fme_id)
    KIND = fme_line
    COERCED -> 3DForcer
Note: Force to 3D so georeferencing / written to SKP
3DForcer
    KEEPZVAL = Yes
    ZVALATTR = 0
    -> Offsetter_2
Offsetter_2
    MODE = Cartesian Coordinate
    XOFF = -731100
    YOFF = -2902900
    ZOFF = 0
    OFFSET -> frame_poly (writer OBJ_2)
Note: Export Frame and Georefrencing Metadata
Note: A GeoJSON version of the frame feature class.
FeatureWriter_2
    DATASET = $(CollectionCatalogFolder)\Frame.geojson
    DATASET_ATTR = _dataset
    FEATURE_TYPE_LIST_ATTR = _feature_type
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
    SUMMARY -> FeatureReader_2 [INITIATOR]
    SUMMARY -> AttributeCreator_2
AttributeCreator_2
    ATTR_TABLE = SET_TO text_line_data = var framePoly =
    -> FeatureWriter_4 [text_line00]
FeatureReader_2
    ATTR_ACCUM_MODE = Only Use Result
    COMBINE_GEOM = Use Result
    DATASET = @Value(_dataset)
    FORMAT = TEXTLINE
    OUTPUT_FEATURES_DISPLAY = Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    <OTHER> -> FeatureHolder_2
FeatureHolder_2
    -> FeatureWriter_4 [text_line]

Bookmark: Buildings Grouped
Note: Group and Export Building Models
Note: Necessarry per SKP Writer Docs
GeometryValidator
    ISSUE_ATTR_NAME = _issues
    PRESETS = Basic Integrity
    REPAIR = Yes
    RULES = NAN_REMOVAL PROCESS_MEASURE]NO]FME_CONTROLLER_QUERY_FILE]transformers\dependencies\geometryvalidator\NAN_REMOVAL.fme NULL_REMOVAL  TYPE_REPAIR CONNECT_Z_MODE]FIRST_WINS]ARC_ENDPOINT_TOLERANCE_MODE]Auto]ARC_ENDPOINT_TOLERANCE]<Unused>]FME_CONTROLLER_QUERY_FILE]transformers\dependencies\geometryvalidator\TYPE_REPAIR.fme
    SUMMARY = Detailed
    PASSED -> AppearanceSetter [GEOMETRY]
    PASSED -> AppearanceStyler
    FAILED -> ListExploder
    REPAIRED -> GeometryPartExtractor_2
    REPAIRED -> ListExploder
    ISSUE_LOCATIONS -> ListExploder
Note: Extract faces from models that behaved abnormally in the GeometryExtractor. This step is necessary for many models seem tobe corrupt somehow. This needs to be looked into.
GeometryPartExtractor_2
    EXTRACTTYPE_PARAM = Extract
    GQUERY:
      for $geom in //geometry
      where $geom/@fme_geometry_type = 'IFMEFace'
      return number($geom/@fme_id)
    PROCESSED -> AppearanceStyler
    PROCESSED -> AppearanceSetter [GEOMETRY]
    UNTOUCHED -> AppearanceStyler
    UNTOUCHED -> AppearanceSetter [GEOMETRY]
Note: Create appearances. For now all face appearances are white. This is because of unpredictable tings happen with multipatch textures.
AppearanceStyler
    ALPHA = 1.0
    APPEARANCE_NAME = White
    DIFFUSE_COLOR = 1,1,1
    SHININESS = 0
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter [APPEARANCE]
Note: Apply appearances by face id
AppearanceSetter
    DEF_STORAGE = Create New Definitions
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Aggregator_6
Note: Groups Model Faces accordng to ModelID
Aggregator_6
    ACCUM_ATTRS_NAME = Get Attributes From One Representative Feature
    AGGREGATE_TYPE = Heterogeneous Collection
    GEOM_NAME_FIELD = Model_ID
    GROUP_BY = Model_ID
    MODE = Geometry - Assemble One Level
    ORDERED = No
    SEP = ,
    AGGREGATE -> Offsetter
Offsetter
    MODE = Cartesian Coordinate
    XOFF = -731100
    YOFF = -2902900
    ZOFF = 0
    OFFSET -> bos3d_models (writer OBJ_1)
Note: A GeoJSON version of the Model Footprints feature class.
FeatureWriter_5
    DATASET = $(TiledCollectionsFolder)\$(Tile_Name)_ModelCollection_OBJ\@Value(Model_ID)_OBJ.zip\@Value(Model_ID)_info.json
    DATASET_ATTR = _dataset
    FEATURE_TYPE_LIST_ATTR = _feature_type
    FORMAT = JSON
    JSON_DESTINATION_DATASETTYPE_VALIDATION = Yes
    JSON_FEATURE_TYPE_KEY = json_featuretype
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = YES
    JSON_WRITE_GEOMETRY = NO
    TOTAL_FEATURES_WRITTEN_ATTR = _total_features_written
    SUMMARY -> bos3d_models (writer OBJ_1)
