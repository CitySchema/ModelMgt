FME workspace Multipatch2Obj_dev3.fmw
Title: Export Tiled Buildings to OBJ

Parameters:
- Tile_Option = @Value(Model_ID)_OBJ   # Check to sort OBJs into Tiles
- Batch_GDB = F:\current_work\projects\Boston\Bos3d\Bos3dDevpbc\Workflows\ModelMgt_CityWide_20220308\ModelWork\udtg_20230130\batch.gdb   # Pick a GDB that contains a toValidate_MP feature class.
- PARAMETER = autoAssembled_MP   # Select a Feature Class to Validate
- OutputModelStore = F:\current_work\projects\Boston\Bos3d\Bos3dDevpbc\Workflows\ModelMgt_CityWide_20220308\ModelWork\udtg_20230130\ModelStore   # Select your ModelStore folder for output.
- DestDataset_GEOJSON = cataalog_poly.json   # Destination GeoJSON File
- obj_writer_output_private = $(OutputModelStore)\obj   # Destination OBJ Folder

Readers:
- GEODATABASE_FILE_6: GEODATABASE_FILE from $(Batch_GDB)

Writers:
- CSV2_2: CSV2 to $(OutputModelStore)
- OBJ_2: OBJ to $(obj_writer_output_private)
- GEOJSON_1: GEOJSON to $(DestDataset_GEOJSON)

toValidate_MP (reader GEODATABASE_FILE_6)
    attributes: OBJECTID integer, Name char(150), StructType char(50), Project_Id double, ProjectLnk char(512), Status char(50), Appear_Dt date, Appear_Src char(254), Disapp_Dt date, Disapp_Src char(254), Model_ID char(15), Model_Cred char(100), ModelBatch char(254), Model_File char(254), Model_Dt date, Model_Note char(254), Model_LOD double, Survey_Dt date, Survey_Src char(150), Centr_Lat double, Centr_Lon double, Centr_X_Ft double, Centr_Y_Ft float, Gnd_El_Ft double, Z_Max_Ft double, Z_MIn_Ft double, Height_Ft double, Tile_ID char(12), Parcel_ID char(15), Struct_ID char(255),
      StructUse char(50), GoogleLnk char(254), NearMapLnk char(254), Struct_Lnk char(255), Parcel_Lnk char(255), Editor char(50), Edit_Dt date, EditAction char(255), QA_Issue char(255), QA_Flag char(255), RecInitUser char(255), RecInitDt date, RecModUser char(255), RecModDt date
    -> AttributeManager
Note: JSON Metadata Record (per model) (Un-tiled Option)
FeatureWriter_3
    DATASET = $(OutputModelStore)\catalog.json
    DATASET_ATTR = _dataset
    FEATURE_TYPE_LIST_ATTR = _feature_type
    FORMAT = JSON
    JSON_DESTINATION_DATASETTYPE_VALIDATION = Yes
    JSON_FEATURE_TYPE_KEY = json_featuretype
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = YES
    JSON_WRITE_GEOMETRY = NO
    TOTAL_FEATURES_WRITTEN_ATTR = _total_features_written
Note: JSON Metadata Record (per model) (Un-tiled Option)
FeatureWriter_2
    DATASET = $(OutputModelStore)\obj\$(Tile_Option)\@Value(Model_ID)_info.json
    DATASET_ATTR = _dataset
    FEATURE_TYPE_LIST_ATTR = _feature_type
    FORMAT = JSON
    JSON_DESTINATION_DATASETTYPE_VALIDATION = Yes
    JSON_FEATURE_TYPE_KEY = json_featuretype
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = YES
    JSON_WRITE_GEOMETRY = NO
    TOTAL_FEATURES_WRITTEN_ATTR = _total_features_written
Note: OBJ Files
toValidate_MP (writer OBJ_2)
Note: Validation Log
FME_Validation_log (writer CSV2_2)
    attributes: Name string, Model_ID string, count string, issue_found string, location_sample.x string, location_sample.y string, location_sample.z string, repair_state string, details string, fme_rejection_code string, _element_index string

Bookmark: Buildings Grouped
AttributeManager
    ATTR_TABLE:
      REMOVE OBJECTID
      SET_TO Model_ID = @Value(Model_ID)
      SET_TO Name = @Value(Name)
      SET_TO StructType = @Value(StructType)
      SET_TO Project_Id = @Value(Project_Id)
      SET_TO ProjectLnk = @Value(ProjectLnk)
      SET_TO Model_Cred = @Value(Model_Cred)
      SET_TO Model_Note = @Value(Model_Note)
      SET_TO Model_LOD = @Value(Model_LOD)
      SET_TO Survey_Dt = @Value(Survey_Dt)
      SET_TO Survey_Src = @Value(Survey_Src)
      SET_TO Centr_Lat = @Value(Centr_Lat)
      SET_TO Centr_Lon = @Value(Centr_Lon)
      SET_TO Centr_X_Ft = @Value(Centr_X_Ft)
      SET_TO Centr_Y_Ft = @Value(Centr_Y_Ft)
      SET_TO Gnd_El_Ft = @Value(Gnd_El_Ft)
      SET_TO Z_Max_Ft = @Value(Z_Max_Ft)
      SET_TO Z_MIn_Ft = @Value(Z_MIn_Ft)
      SET_TO Tile_ID = @Value(Tile_ID)
      SET_TO Parcel_ID
    -> GeometryValidator
    -> NullAttributeMapper_3
Note: Transform Multipatch to ModelStore
NullAttributeMapper_3
    ATTRCHOICE = Selected Attributes
    ATTRLIST = Centr_Lat Centr_Lon Centr_X_Ft Centr_Y_Ft Edit_Dt EditAction Editor Model_Dt Model_ID Model_Note ModelBatch Name StructType Survey_Dt Tile_ID Z_Max_Ft Z_MIn_Ft
    NULL_TREATMENT = Null
    REG_EXP = /^\s*$/
    SOURCE_ATTR_VAL = Empty "Missing (Selected Attributes Only)" Null
    -> FeatureWriter_2 [<All>]
    -> FeatureWriter_3 [<All>]
GeometryValidator
    ISSUE_ATTR_NAME = _issues
    PRESETS = Custom
    REPAIR = Yes
    RULES = NAN_REMOVAL PROCESS_MEASURE]NO]FME_CONTROLLER_QUERY_FILE]transformers/dependencies/geometryvalidator/NAN_REMOVAL.fme]FME_CONTROLLER_CHOICE]NAN_REMOVAL NULL_REMOVAL FME_CONTROLLER_QUERY_FILE]transformers/dependencies/geometryvalidator/NULL_REMOVAL.fme]FME_CONTROLLER_CHOICE]NULL_REMOVAL TYPE_REPAIR CONNECT_Z_MODE]LAST_WINS]ARC_ENDPOINT_TOLERANCE_MODE]Custom]ARC_ENDPOINT_TOLERANCE]0.1]FME_CONTROLLER_QUERY_FILE]transformers/dependencies/geometryvalidator/TYPE_REPAIR.fme]FME_CONTROLLER_CHOICE]TYPE_REPAIR
    SUMMARY = Detailed
    PASSED -> GeometryPartExtractor_2
    PASSED -> SurfaceFootprintReplacer
    FAILED -> ListExploder
    FAILED -> SurfaceFootprintReplacer
    REPAIRED -> GeometryPartExtractor_2
    INVALID_PARTS -> ListExploder
Note: Extract faces from models that behaved abnormally in the GeometryExtractor. This step is necessary for many models seem tobe corrupt somehow. This needs to be looked into. / I think that the 10 things that were not extracted were the mesh
GeometryPartExtractor_2
    EXTRACTTYPE_PARAM = Extract
    GQUERY:
      for $geom in //geometry
      where $geom/@fme_geometry_type = 'IFMEFace'
      return number($geom/@fme_id)
    PROCESSED -> AppearanceStyler
    UNTOUCHED -> AppearanceStyler
    UNTOUCHED -> AppearanceSetter [GEOMETRY]
Note: Create appearances. For now all face appearances are white. This is because of unpredictable tings happen with multipatch textures.
AppearanceStyler
    ALPHA = 1.0
    APPEARANCE_NAME = White
    DIFFUSE_COLOR = 1,1,1
    SHININESS = 0
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter [APPEARANCE]
    -> AppearanceSetter [GEOMETRY] [off]
Note: Apply appearances by face id
AppearanceSetter
    DEF_STORAGE = Create New Definitions
    SET_ON_SIDE = Front Side
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Aggregator_6
Note: re-groups Model Faces accordng to ModelID
Aggregator_6
    ACCUM_ATTRS_NAME = Get Attributes From One Representative Feature
    AGGREGATE_TYPE = Heterogeneous Collection
    GEOM_NAME_FIELD = Model_ID
    GROUP_BY = Model_ID
    MODE = Geometry - Assemble One Level
    ORDERED = No
    SEP = ,
    AGGREGATE -> Offsetter
Note: Shift to Metro3D Coordinate Origin
Offsetter
    MODE = Cartesian Coordinate
    XOFF = -731100
    YOFF = -2902900
    ZOFF = 0
    OFFSET -> toValidate_MP (writer OBJ_2)
SurfaceFootprintReplacer
    OFFSET_Z = 0
    SHADOW_MODE = Overhead Shadow
Note: Write Error log for geometry validator rejects. / An attribute may fail multiple testsList Exploder / Splits the list to create one record per test message
ListExploder
    ATTR_ACCUM_MODE = Merge List Attributes
    ATTR_CONFLICT_RES = Use List Attribute Values
    INDEX_ATTR = _element_index
    LIST_ATTR = _issues{}
    ELEMENTS -> FME_Validation_log (writer CSV2_2)
    <REJECTED> -> FME_Validation_log (writer CSV2_2)
toValidate_MP (writer GEOJSON_1)
    attributes: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
