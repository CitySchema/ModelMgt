FME workspace gdb_mp2obj.fmw

Parameters:
- BatchFolder = F:\current_work\projects\Boston\Bos3d\Bos3dDevpbc\Workflows\ModelMgt_20201214\ModelWork\testing   # Output Folder
- GeoDatabase = F:\current_work\projects\Boston\Bos3d\Bos3dDevpbc\Workflows\ModelMgt_20201214\Scratch\Scratch.gdb   # Geodatabase that includes a ToEdit feature class
- DestDataset_CSV = $(BatchFolder)\fme_qc_report.csv   # Destination CSV (CommaSeparatedValue) Folder
- SourceDataset_GEODATABASE_FILE = $(GeoDatabase)   # File Geodatabase

Readers:
- GEODATABASE_FILE_1: GEODATABASE_FILE from F:\current_work\projects\Boston\Bos3d\Bos3dDevpbc\Workflows\ModelMgt_20201214\Stage\Edits.gdb in MA83F
- GEODATABASE_FILE_2: GEODATABASE_FILE from $(SourceDataset_GEODATABASE_FILE)

Writers:
- OBJ_1: OBJ to $(BatchFolder)
- SKP_1: SKP to $(BatchFolder) in MA83F
- CSV_1: CSV to $(DestDataset_CSV)

testedits_masp (reader GEODATABASE_FILE_1) [off]
    attributes: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
ToExport (reader GEODATABASE_FILE_2)
    attributes: OBJECTID integer, Name char(150), Struct_ID char(255), StructType char(50), StructUse char(50), StructLink char(255), Project_Id double, ProjectLnk char(512), Status char(50), Appear_Dt date, Appear_Src char(254), Disapp_Dt date, Disapp_Src char(254), Editor char(50), Edit_Dt date, EditAction char(255), Model_ID char(15), Model_Cred char(100), ModelBatch char(254), Model_File char(254), Model_Dt date, Model_Note char(254), Model_LOD double, Survey_Dt date, Survey_Src char(150), Centr_Lat double, Centr_Lon double, Gnd_El_Ft double, Z_Max_Ft double, Z_MIn_Ft double,
      Height_Ft double, Tile_ID char(12), Parcel_ID char(15), GoogleLnk char(254), NearMapLnk char(254), chgEditor char(50), chgEditDt date, chgAction char(255), chgStatus char(255), chgStatDt date, chgStatSrc char(255), chgQAIssue char(255), chgCandid8 char(50), ChgDestFC char(255)
    -> Offsetter
Offsetter
    MODE = Cartesian Coordinate
    XOFF = -731100
    YOFF = -2902900
    ZOFF = 0
    OFFSET -> 3DRotator
3DRotator
    ANGLE = -90
    AXIS_CHOICE = X Axis
    ROTATED -> GeometryValidator
    ROTATED -> AppearanceSetter [GEOMETRY]
GeometryValidator
    ISSUE_ATTR_NAME = _issues
    PRESETS = Custom
    REPAIR = No
    RULES = SURFACE_ORIENTATION  CONSECUTIVE_IDENTICAL_VERTICES_2D CHECK_Z]YES]TOLERANCE]0.2]FME_CONTROLLER_QUERY_FILE]transformers/dependencies/geometryvalidator/CONSECUTIVE_IDENTICAL_VERTICES_2D.fme NAN_REMOVAL PROCESS_MEASURE]YES]FME_CONTROLLER_QUERY_FILE]transformers/dependencies/geometryvalidator/NAN_REMOVAL.fme PLANAR_SURFACE CHECK_AREA]DO_NOT_CHECK_AREA]TOLERANCE_MODE]AUTO]TOLERANCE]0.0]ANGULAR_TOLERANCE_MODE]Automatic]ANGULAR_TOLERANCE]0.0]FME_CONTROLLER_QUERY_FILE]transformers/dependencies/geometryvalidator/PLANAR_SURFACE.fme AREA_ORIENTATION AREA_ORIENTATION]RIGHT]FME_CONTROLLER_QUERY_FILE]transformers/dependencies/geometryvalidator/AREA_ORIENTATION.fme TYPE_REPAIR CONNECT_Z_MODE]IGNORE_Z]ARC_ENDPOINT_TOLERANCE_MODE]Auto]ARC_ENDPOINT_TOLERANCE]<Unused>]FME_CONTROLLER_QUERY_FILE]transformers/dependencies/geometryvalidator/TYPE_REPAIR.fme MISMATCHED_DIMENSIONS FORCE_DIMENSION]3D]MISMATCHED_Z_VAL]0]FME_CONTROLLER_QUERY_FILE]transformers/dependencies/geometryvalidator/MISMATCHED_DIMENSIONS.fme
    SUMMARY = Detailed
    FAILED -> ListExploder
    FAILED -> GeometryValidator__Rejected_
    REPAIRED -> ListExploder
    <REJECTED> -> ListExploder
GeometryValidator__Rejected_: Inspector
Note: Apply appearances by face id
AppearanceSetter
    DEF_STORAGE = Create New Definitions
    DIFFUSE_COLOR = 1,1,1
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> test3do_b4edits (writer OBJ_1)
    -> AttributeCreator_3
    <REJECTED> -> AttributeCreator_3
    <REJECTED> -> test3do_b4edits (writer OBJ_1)
test3do_b4edits (writer SKP_1)
Note: Create appearances
AppearanceStyler
    ALPHA = 1.0
    APPEARANCE_NAME = Ground
    DIFFUSE_COLOR = 1,1,1
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V

Bookmark: Detailed Validation Report
Note: ListExploder / An attribute may fail multiple tests / Split the list to create one record per test message
ListExploder
    ATTR_ACCUM_MODE = Merge List Attributes
    ATTR_CONFLICT_RES = Use List Attribute Values
    INDEX_ATTR = _element_index
    LIST_ATTR = _issues{}
    ELEMENTS -> AttributeManager_2
    <REJECTED> -> AttributeManager_2
AttributeManager_2
    ATTR_TABLE:
      RENAME_SET_VALUE _element_index > messageNumber
      REMOVE StructType
      REMOVE StructUse
      REMOVE StructLink
      REMOVE Status
      REMOVE Appear_Dt
      REMOVE Appear_Src
      REMOVE Disapp_Dt
      REMOVE Disapp_Src
      REMOVE Editor
      REMOVE Edit_Dt
      REMOVE EditAction
      REMOVE Model_Note
      REMOVE Model_LOD
      REMOVE Survey_Dt
      REMOVE Survey_Src
      REMOVE Centr_Lat
      REMOVE Centr_Lon
      REMOVE Gnd_El_Ft
      REMOVE Z_Max_Ft
      REMOVE Z_MIn_Ft
      REMOVE Height_Ft
      REMOVE GoogleLnk
      REMOVE NearMapLnk
      REMOVE chgEditor
      REMOVE chgEditDt
      REMOVE chgAction
      REMOVE chgStatus
      REMOVE chgStatDt
      REMOVE chgStatSrc
      REMOVE chgQAIssue
      REMOVE chgCandid8
      SET_TO issue_found = @Value(issue_found)
      REMOVE location_sample.x
      REMOVE location_sample.y
      REMOVE location_sample.z
      SET_TO repair_state = @Value(repair_state)
      SET_TO fme_rejection_code = @Value(fme_rejection_code)
    -> ValidationReport (writer CSV_1)
ValidationReport (writer CSV_1)
    attributes: messageNumber text, OBJECTID int, Name text, Model_ID text, ModelBatch text, Model_File text, Model_Dt char(20), count text, issue_found text, repair_state text, fme_rejection_code text, Struct_ID text, Project_Id float, ProjectLnk text, Model_Cred text, Tile_ID text, Parcel_ID text, ChgDestFC text

Bookmark: Writer Feature Types
test3do_b4edits (writer OBJ_1)

Bookmark: Create Buildings Layer
AttributeCreator_3
    ATTR_TABLE = SET_TO sketchup_layer_name = ToEdit
    -> GeometryPropertySetter_5
GeometryPropertySetter_5
    GQUERY:
      for $geom in //geometry
      where $geom/count(parent::geometry) = 0
      return number($geom/@fme_id)
    OVERWRITE_CHOICE = Yes
    REMOVE_ATTRIBUTE = No
    SETTYPE_PARAM = Traits From Attributes
    SRC_ATTRS = sketchup_layer_name
    SET -> test3do_b4edits (writer SKP_1)
