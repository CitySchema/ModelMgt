FME workspace ModelStore2Multipatch_New.fmw

Parameters:
- ModelStore = F:\current_work\projects\Boston\Bos3d\Bos3dDevpbc\Workflows\ModelMgtBPDA-20230228_v4\ModelWork\cc3d_LibraryUpdates_20221017\ModelStore   # Select Input ModelStore folder
- Output_GDB = F:\current_work\projects\Boston\Bos3d\Bos3dDevpbc\Workflows\ModelMgtBPDA-20230228_v4\ModelWork\cc3d_LibraryUpdates_20221017\Batch.gdb   # Destination File GDB
- DestinationFCName = FME_Validated_MP   # Destination FC Name
- SourceDataset_GEODATABASE_FILE = F:\current_work\projects\Boston\Bos3d\Bos3dDevpbc\Workflows\ModelMgtBPDA-20230228_v4\ModelWork\cc3d_LibraryUpdates_20221017\Batch.gdb   # File Geodatabase
- SourceDataset_OBJ = $(ModelStore)\**\*.obj   # Source OBJ File

Readers:
- OBJ_2: OBJ from $(SourceDataset_OBJ) in EPSG:2249
- GEODATABASE_FILE_3: GEODATABASE_FILE from $(SourceDataset_GEODATABASE_FILE)

Writers:
- GEODATABASE_FILE_1: GEODATABASE_FILE to $(Output_GDB)
- CSV2_1: CSV2 to $(ModelStore)
- GEODATABASE_FILE_2: GEODATABASE_FILE to $(Output_GDB)
- CSV2_2: CSV2 to $(ModelStore) in EPSG:2249

AttributeFileReader
    CHAR_ENCODING = fme-binary
    DEST_ATTR = _file_contents
DatabaseJoiner [off]
    ATTR_ACCUM_MODE = Merge Joined
    ATTR_CONFLICT_RES = Use Original
    DATASET = F:\current_work\projects\Boston\Bos3d\Bos3dDevpbc\Workflows\ModelMgtBPDA-20230228_v4\ModelWork\cc3d_LibraryUpdates_20221017\Batch.gdb
    FILEGDB_QUERY_FEATURE_TYPES_FOR_MERGE_FILTERS = Yes
    FORMAT = FILEGDB
    JOIN_KEYS = "_filename "
    MATCH_MULTIPLE_DISPLAY = Create a feature for each match
    MATCH_RULE_DISPLAY = Match All (1:M)
    TABLE = Ready_MP
Ready_MP (reader GEODATABASE_FILE_3)
    attributes: OBJECTID integer, Name char(150), StructType char(50), Project_ID char(25), ProjectLnk char(512), Status char(50), Appear_Dt date, Appear_Src char(254), Disapp_Dt date, Disapp_Src char(254), Model_ID char(50), Model_Cred char(100), Model_LOD double, Survey_Src char(150), Survey_Dt date, Model_Note char(254), Model_Dt date, ModelBatch char(254), Model_File char(254), ModelStore char(25), Centr_Lat double, Centr_Lon double, Centr_X_Ft double, Centr_Y_Ft float, Gnd_El_Ft double, Z_Max_Ft double, Z_MIn_Ft double, Height_Ft double, Tile_ID char(12), GoogleLnk char(254),
      NearMapLnk char(254), Parcel_ID char(15), Parcel_Lnk char(255), Struct_ID char(255), StructUse char(50), Struct_Lnk char(255), Editor char(50), Edit_Dt date, EditAction char(255), QA_Issue char(255), QA_Flag char(255), RecInitUser char(255), RecInitDt date, RecModUser char(255), RecModDt date
    -> FeatureJoiner [RIGHT]
Note: This workbench reads all of the OBJ files in the user-specified ModelStore and writes them to a multipatch feature class. Validation logs are written to recored any repairs that were made or unrecoverable errors.
Note: Read all OBJ files in user-specified ModelStore folder.
BOS-00NUE-OWDJF-XX898 (reader OBJ_2)
    -> FilenamePartExtractor
FilenamePartExtractor
    DIRNAME_ATTR = _dirname
    DIRPATH_ATTR = _dirpath
    EXTENSION_ATTR = _extension
    FULLNAME_ATTR = _filename
    ROOTNAME_ATTR = _rootname
    SRC_ATTR = @Value(fme_feature_type)
    -> FeatureJoiner [LEFT]
FeatureJoiner
    ATTR_CONFLICT_RES = Prefer Left
    GEOMETRY_HANDLING = Prefer Left
    JOIN_KEYS = _rootname Model_ID AUTO
    JOIN_MODE = Inner
    JOINED -> Offsetter
Note: Offset models to Mass State Plane Feet.
Offsetter
    MODE = Cartesian Coordinate
    XOFF = 731100
    YOFF = 2902900
    ZOFF = 0
    OFFSET -> EsriReprojector
EsriReprojector
    DEST = ESRIWKT|NAD_1983_2011_StatePlane_Massachusetts_Mnld_FIPS_2001_FtUS|PROJCS["NAD_1983_2011_StatePlane_Massachusetts_Mnld_FIPS_2001_FtUS",GEOGCS["GCS_NAD_1983_2011",DATUM["D_NAD_1983_2011",SPHEROID["GRS_1980",6378137.0,298.257222101]],PRIMEM["Greenwich",0.0],UNIT["Degree",0.0174532925199433]],PROJECTION["Lambert_Conformal_Conic"],PARAMETER["False_Easting",656166.6666666665],PARAMETER["False_Northing",2460625.0],PARAMETER["Central_Meridian",-71.5],PARAMETER["Standard_Parallel_1",41.71666666666667],PARAMETER["Standard_Parallel_2",42.68333333333333],PARAMETER["Latitude_Of_Origin",41.0],UNIT["Foot_US",0.3048006096012192]]
    GEOTRANSFORMATION_NAME = <None>
    INTERPOLATION_TYPE_NAME = Nearest Neighbor
    RASTER_CELL_SIZE = Preserve Cells
    RASTER_TOLERANCE = 0.0
    SOURCE = ESRIWKT|NAD_1983_2011_StatePlane_Massachusetts_Mnld_FIPS_2001_FtUS|PROJCS["NAD_1983_2011_StatePlane_Massachusetts_Mnld_FIPS_2001_FtUS",GEOGCS["GCS_NAD_1983_2011",DATUM["D_NAD_1983_2011",SPHEROID["GRS_1980",6378137.0,298.257222101]],PRIMEM["Greenwich",0.0],UNIT["Degree",0.0174532925199433]],PROJECTION["Lambert_Conformal_Conic"],PARAMETER["False_Easting",656166.6666666665],PARAMETER["False_Northing",2460625.0],PARAMETER["Central_Meridian",-71.5],PARAMETER["Standard_Parallel_1",41.71666666666667],PARAMETER["Standard_Parallel_2",42.68333333333333],PARAMETER["Latitude_Of_Origin",41.0],UNIT["Foot_US",0.3048006096012192]]
    VERTICAL_HANDLING = Use Vertical Transformation
    VERTTRANSFORMATION_NAME = <None>
    VERT_DEST = ESRIWKT|NAVD88_height_(ftUS)|VERTCS["NAVD88_height_(ftUS)",VDATUM["North_American_Vertical_Datum_1988"],PARAMETER["Vertical_Shift",0.0],PARAMETER["Direction",1.0],UNIT["Foot_US",0.3048006096012192]]
    VERT_SOURCE = ESRIWKT|NAVD88_height_(ftUS)|VERTCS["NAVD88_height_(ftUS)",VDATUM["North_American_Vertical_Datum_1988"],PARAMETER["Vertical_Shift",0.0],PARAMETER["Direction",1.0],UNIT["Foot_US",0.3048006096012192]]
    REPROJECTED -> GeometryValidator
Note: Before running this, you must make sure that the FME_Validated_MP feature class and the FMELOG_Tbl are not open in ArcGIS Pro. After closing or deletfing these, save your project.
GeometryValidator
    ISSUE_ATTR_NAME = _issues
    PRESETS = Custom
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR SURFACE_ORIENTATION FME_CONTROLLER_QUERY_FILE]transformers/dependencies/geometryvalidator8/SURFACE_ORIENTATION.fme]FME_CONTROLLER_CHOICE]SURFACE_ORIENTATION
    SUMMARY = Detailed
    PASSED -> FME_FromOBJ_MP (writer GEODATABASE_FILE_1)
    FAILED -> FME_FromOBJ_MP (writer GEODATABASE_FILE_1)
    FAILED -> ListExploder
    REPAIRED -> FME_FromOBJ_MP (writer GEODATABASE_FILE_1)
    REPAIRED -> ListExploder
    ISSUE_LOCATIONS -> ListExploder
Note: Write Geodatabase Feature Class
FME_FromOBJ_MP (writer GEODATABASE_FILE_1)
    attributes: _rootname char(2048)
Note: List Exploder splits the list of issues per feature into one table row per issue.
ListExploder
    ATTR_ACCUM_MODE = Merge List Attributes
    ATTR_CONFLICT_RES = Use List Attribute Values
    INDEX_ATTR = _element_index
    LIST_ATTR = _issues{}
    ELEMENTS -> NullAttributeMapper
Note: When Repair Status is Null, change it to "Repaired"
NullAttributeMapper
    ATTRCHOICE = Selected Attributes
    ATTRLIST = repair_state
    NEW_VALUE = Repaired
    NULL_TREATMENT = New Value
    SOURCE_ATTR_VAL = Null
    -> StatisticsCalculator
Note: Groups redundnat rows with same issue and feature into one row with count.
StatisticsCalculator
    CALCULATION_MODE = NUMERIC
    FEAT_STATS = issue_found,NUMERIC_MODE,,,COUNT,,,,,,,,,,
    GROUP_BY = issue_found location_sample.x location_sample.y location_sample.z repair_state _rootname
    SUMMARY -> OBJ2GDB_Validation_log (writer CSV2_2)
    SUMMARY -> OBJ2GDB_ValidationLog_TBL (writer GEODATABASE_FILE_2)
Note: Write validation log to Geodatabase
OBJ2GDB_ValidationLog_TBL (writer GEODATABASE_FILE_2)
    attributes: _rootname char(2048), issue_found char(2048), location_sample_x double, location_sample_y double, location_sample_z double, repair_state char(2048), issue_found_total_count char(20)
OBJ2GDB_Validation_log (writer CSV2_2)
    attributes: _rootname string, issue_found string, location_sample.x real64, location_sample.y real64, location_sample.z real64, repair_state string, issue_found.total_count uint64
